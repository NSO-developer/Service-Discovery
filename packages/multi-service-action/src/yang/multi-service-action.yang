module multi-service-action {
  yang-version "1.1";

  namespace "http://example.com/multi-service-action";
  prefix multi-service-action;

  import ietf-inet-types {
    prefix inet;
  }
  import tailf-common {
    prefix tailf;
  }
  import tailf-ncs {
    prefix ncs;
  }
  
  grouping multi-service-actions {
    action re-deploy {
      tailf:actionpoint msa-re-deploy;
      input {
        container dry-run {
          presence "";
          leaf outformat {
            type ncs:outformat3;
          }
        }
        uses ncs:ncs-commit-params;
        uses ncs:service-depth {
          refine "depth/deep" {
            description "Recursively 're-deploy' stacked services";
          }
          refine "depth/shallow" {
            description "Only 're-deploy' the topmost service";
          }
        }
        container reconcile {
          description
            "Reconcile the service data. All data which existed before
            the service was created will now be owned by the service.
            The reference count will indicate how many services control
            the data. When the service is removed that data will also be
            removed. In technical terms the reference count will be
            decreased by one for everything which existed prior to the
            service.

            If manually configured data exists below in the configuration
            tree that data is kept unless the option
            'discard-non-service-config' is used.";
          presence "";
          choice c-non-service-config {
            leaf keep-non-service-config {
              type empty;
            }
            leaf discard-non-service-config {
              type empty;
            }
            default keep-non-service-config;
          }
        }
      }
      output {
        list service {
          key name;
          leaf name {
            type string;
          }
          choice outformat {
            case case-xml {
              uses ncs:dry-run-xml;
            }
            case case-cli {
              uses ncs:dry-run-cli;
            }
            case case-cli-c {
              uses ncs:dry-run-cli-c;
            }
            case case-native {
              uses ncs:dry-run-native;
            }
          }
          uses ncs:ncs-commit-result;
        }
      }
    }

    action check-sync {
      tailf:actionpoint msa-check-sync;
      input {
        leaf outformat {
          type ncs:outformat4;
          default boolean;
        }
        uses ncs:service-depth {
          refine "depth/deep" {
            description "Recursively 'check-sync' stacked services";
          }
          refine "depth/shallow" {
            description "Only 'check-sync' the topmost service";
          }
        }
        leaf suppress-positive-result {
          type empty;
          tailf:info "Return list only contains negatives";
          description
            "Use this additional parameter to only return services that
            failed to sync.";
        }
        uses ncs:choice-lsa-grouping;
      }
      output {
        list service {
          key name;
          leaf name {
            type string;
          }
          uses ncs:service-check-sync-result;
        }
      }
    }
  }

}
